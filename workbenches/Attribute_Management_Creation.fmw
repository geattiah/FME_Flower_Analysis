FME workspace Attribute_Management_Creation.fmw

Parameters:
- DestDataset_SHAPEFILE = /home/gift/Documents/git_projects/FME/FME_Flower_Analysis/Shapefiles   # Destination Esri Shapefile Folder
- SourceDataset_SHAPEFILE_7 = /home/gift/Documents/git_projects/fme/fme_flower_analysis/shapefiles_Data/Flower_Data.shp   # Source Esri Shapefile(s)
- DestDataset_SHAPEFILE_3 = /home/gift/Documents/git_projects/fme/fme_flower_analysis/output_shapefiles   # Destination Esri Shapefile Folder

Readers:
- SHAPEFILE_6: SHAPEFILE from $(SourceDataset_SHAPEFILE_7)

Writers:
- SHAPEFILE_2: SHAPEFILE to $(DestDataset_SHAPEFILE)
- SHAPEFILE_1: SHAPEFILE to $(DestDataset_SHAPEFILE_3)

Flower_Data (reader SHAPEFILE_6)
    attributes: Flower char(254), F_Count number(11,0), F_Shape char(254), Month char(200), Day char(200), Year char(200), Key char(200), Developed char(254), Latitude double, Longitude double, Location char(254)
    -> Developed_filter
Developed_filter: AttributeFilter
    ATTR_NAME = Developed
    ATTR_VALUES = <Empty>,<Missing>,<Null>,<Unfiltered>,No,Yes
    <EMPTY> -> Junction
    <MISSING> -> Junction
    <NULL> -> Junction
    <UNFILTERED> -> Junction
    No -> Junction
    Yes -> Junction
Junction
    -> F_Shape_filter
F_Shape_filter: AttributeFilter
    ATTR_NAME = F_Shape
    ATTR_VALUES = <Empty>,<Missing>,<Null>,<Unfiltered>,Arrow,Circle,Crescent,Cross,Cube,Cylinder,Heart,Heptagon,Hexagon,Nonagon,Octagon,Oval,Parallelogram,Pentagon,Rhombus,Right_triangle,Scalene_triangle,Square,Star,Triangle,Unknown
    <EMPTY> -> Junction_2
    <MISSING> -> Junction_2
    <NULL> -> Junction_2
    <UNFILTERED> -> Junction_2
    Arrow -> Junction_2
    Circle -> Junction_2
    Crescent -> Junction_2
    Cross -> Junction_2
    Cube -> Junction_2
    Cylinder -> Junction_2
    Heart -> Junction_2
    Heptagon -> Junction_2
    Hexagon -> Junction_2
    Nonagon -> Junction_2
    Octagon -> Junction_2
    Oval -> Junction_2
    Parallelogram -> Junction_2
    Pentagon -> Junction_2
    Rhombus -> Junction_2
    Right_triangle -> Junction_2
    Scalene_triangle -> Junction_2
    Square -> Junction_2
    Star -> Junction_2
    Triangle -> Junction_2
    Unknown -> Junction_2
Junction_2
    -> Flower_count
Flower_count: AttributeFilter
    ATTR_NAME = F_Count
    ATTR_VALUES = <Empty>,<Missing>,<Null>,<Unfiltered>,No,Yes,0,1,10,100,101,11,110,12,120,124,13,130,139,14,15,150,154,16,17,18,180,19,192,193,2,20,200,2000,201,21,210,22,23,237,24,244,25,250,26,264,27,270,28,280,29,3,30,300,31,32,33,34,35,36,360,37,38,39,4,40,400,41,42,43,44,45,46,47,48,49,5,50,51,52,53,54,55,56,57,58,59,6,60,61,62,63,65,66,68,69,7,70,71,72,74,75,76,77,8,80,81,84,85,86,89,9,90,91,94,95,98
    <EMPTY> -> Junction_3
    <MISSING> -> Junction_3
    <NULL> -> Junction_3
    <UNFILTERED> -> Junction_3
    No -> Junction_3
    Yes -> Junction_3
    0 -> Junction_3
    1 -> Junction_3
    10 -> Junction_3
    100 -> Junction_3
    101 -> Junction_3
    11 -> Junction_3
    110 -> Junction_3
    12 -> Junction_3
    120 -> Junction_3
    124 -> Junction_3
    13 -> Junction_3
    130 -> Junction_3
    139 -> Junction_3
    14 -> Junction_3
    15 -> Junction_3
    150 -> Junction_3
    154 -> Junction_3
    16 -> Junction_3
    17 -> Junction_3
    18 -> Junction_3
    180 -> Junction_3
    19 -> Junction_3
    192 -> Junction_3
    193 -> Junction_3
    2 -> Junction_3
    20 -> Junction_3
    200 -> Junction_3
    2000 -> Junction_3
    201 -> Junction_3
    21 -> Junction_3
    210 -> Junction_3
    22 -> Junction_3
    23 -> Junction_3
    237 -> Junction_3
    24 -> Junction_3
    244 -> Junction_3
    25 -> Junction_3
    250 -> Junction_3
    26 -> Junction_3
    264 -> Junction_3
    27 -> Junction_3
    270 -> Junction_3
    28 -> Junction_3
    280 -> Junction_3
    29 -> Junction_3
    3 -> Junction_3
    30 -> Junction_3
    300 -> Junction_3
    31 -> Junction_3
    32 -> Junction_3
    33 -> Junction_3
    34 -> Junction_3
    35 -> Junction_3
    36 -> Junction_3
    360 -> Junction_3
    37 -> Junction_3
    38 -> Junction_3
    39 -> Junction_3
    4 -> Junction_3
    40 -> Junction_3
    400 -> Junction_3
    41 -> Junction_3
    42 -> Junction_3
    43 -> Junction_3
    44 -> Junction_3
    45 -> Junction_3
    46 -> Junction_3
    47 -> Junction_3
    48 -> Junction_3
    49 -> Junction_3
    5 -> Junction_3
    50 -> Junction_3
    51 -> Junction_3
    52 -> Junction_3
    53 -> Junction_3
    54 -> Junction_3
    55 -> Junction_3
    56 -> Junction_3
    57 -> Junction_3
    58 -> Junction_3
    59 -> Junction_3
    6 -> Junction_3
    60 -> Junction_3
    61 -> Junction_3
    62 -> Junction_3
    63 -> Junction_3
    65 -> Junction_3
    66 -> Junction_3
    68 -> Junction_3
    69 -> Junction_3
    7 -> Junction_3
    70 -> Junction_3
    71 -> Junction_3
    72 -> Junction_3
    74 -> Junction_3
    75 -> Junction_3
    76 -> Junction_3
    77 -> Junction_3
    8 -> Junction_3
    80 -> Junction_3
    81 -> Junction_3
    84 -> Junction_3
    85 -> Junction_3
    86 -> Junction_3
    89 -> Junction_3
    9 -> Junction_3
    90 -> Junction_3
    91 -> Junction_3
    94 -> Junction_3
    95 -> Junction_3
    98 -> Junction_3
Junction_3
    -> Flower_Colour
Flower_Colour: AttributeFilter
    ATTR_NAME = Flower
    ATTR_VALUES:
      <Empty>,<Missing>,<Null>,<Unfiltered>,Baby blue
      ,Amaranth,Amber,Ametheyst,Apricot,Aquamarine,Beige,Black,Blue,Blue_green,Blue_violet,Blush,Bronze,Brown,Burgundy,Byzantium,Carmine,Cerise,Cerulean,Champagne,Chartreuse_green,Chocolate,Cobalt_blue,Coffee,Copper,Coral,Crimson,Cyan,Dessert_sand,Electric_blue,Emerald,Erin,Gold,Gray,Green,Harlequin,Indigo,Ivory,Jade,Jungle_green,Lavender,Lemon,Lilac,Lime,Magenta,Magenta_rose,Maroon,Mauve,Navy_blue,Ochre,Olive,Orange,Orange_red,Orchid,Peach,Pear,Periwinkle,Pink,Plum,Puce,Purple,Raspberry,Red,Rose,Ruby,Salmon,Sangria,Sapphire,Scarlet,Silver,Slate_gray,Spring_bud,Tan,Taupe,Teal,Turquoise,Ultramarine,Violet,Viridian,White,Yellow
    <EMPTY> -> Junction_4
    <MISSING> -> Junction_4
    <NULL> -> Junction_4
    <UNFILTERED> -> Junction_4
    Baby blue -> Junction_4
    Amaranth -> Junction_4
    Amber -> Junction_4
    Ametheyst -> Junction_4
    Apricot -> Junction_4
    Aquamarine -> Junction_4
    Beige -> Junction_4
    Black -> Junction_4
    Blue -> Junction_4
    Blue_green -> Junction_4
    Blue_violet -> Junction_4
    Blush -> Junction_4
    Bronze -> Junction_4
    Brown -> Junction_4
    Burgundy -> Junction_4
    Byzantium -> Junction_4
    Carmine -> Junction_4
    Cerise -> Junction_4
    Cerulean -> Junction_4
    Champagne -> Junction_4
    Chartreuse_green -> Junction_4
    Chocolate -> Junction_4
    Cobalt_blue -> Junction_4
    Coffee -> Junction_4
    Copper -> Junction_4
    Coral -> Junction_4
    Crimson -> Junction_4
    Cyan -> Junction_4
    Dessert_sand -> Junction_4
    Electric_blue -> Junction_4
    Emerald -> Junction_4
    Erin -> Junction_4
    Gold -> Junction_4
    Gray -> Junction_4
    Green -> Junction_4
    Harlequin -> Junction_4
    Indigo -> Junction_4
    Ivory -> Junction_4
    Jade -> Junction_4
    Jungle_green -> Junction_4
    Lavender -> Junction_4
    Lemon -> Junction_4
    Lilac -> Junction_4
    Lime -> Junction_4
    Magenta -> Junction_4
    Magenta_rose -> Junction_4
    Maroon -> Junction_4
    Mauve -> Junction_4
    Navy_blue -> Junction_4
    Ochre -> Junction_4
    Olive -> Junction_4
    Orange -> Junction_4
    Orange_red -> Junction_4
    Orchid -> Junction_4
    Peach -> Junction_4
    Pear -> Junction_4
    Periwinkle -> Junction_4
    Pink -> Junction_4
    Plum -> Junction_4
    Puce -> Junction_4
    Purple -> Junction_4
    Raspberry -> Junction_4
    Red -> Junction_4
    Rose -> Junction_4
    Ruby -> Junction_4
    Salmon -> Junction_4
    Sangria -> Junction_4
    Sapphire -> Junction_4
    Scarlet -> Junction_4
    Silver -> Junction_4
    Slate_gray -> Junction_4
    Spring_bud -> Junction_4
    Tan -> Junction_4
    Taupe -> Junction_4
    Teal -> Junction_4
    Turquoise -> Junction_4
    Ultramarine -> Junction_4
    Violet -> Junction_4
    Viridian -> Junction_4
    White -> Junction_4
    Yellow -> Junction_4
Junction_4
    -> Year_recorded
Year_recorded: AttributeFilter
    ATTR_NAME = Year
    ATTR_VALUES = <Empty>,<Missing>,<Null>,<Unfiltered>,2014,2015,2016,2017,2018,2019
    <EMPTY> -> Junction_5
    <MISSING> -> Junction_5
    <NULL> -> Junction_5
    <UNFILTERED> -> Junction_5
    2014 -> Junction_5
    2015 -> Junction_5
    2016 -> Junction_5
    2017 -> Junction_5
    2018 -> Junction_5
    2019 -> Junction_5
Junction_5
    -> Location
Location: AttributeFilter
    ATTR_NAME = Location
    ATTR_VALUES = <Empty>,<Missing>,<Null>,<Unfiltered>,Exact_location,Exact_location_group,Group,Half_minute_away,Middle_of_group,Town_point
    <EMPTY> -> Junction_6
    <MISSING> -> Junction_6
    <NULL> -> Junction_6
    <UNFILTERED> -> Junction_6
    Exact_location -> Junction_6
    Exact_location_group -> Junction_6
    Group -> Junction_6
    Half_minute_away -> Junction_6
    Middle_of_group -> Junction_6
    Town_point -> Junction_6
Junction_6
    -> Rename
Rename: AttributeManager
    ATTR_TABLE:
      RENAME_SET_VALUE Flower > Flower_colour
      RENAME_SET_VALUE F_Count > Flower_Count
      RENAME_SET_VALUE F_Shape > Flower_Shape
      RENAME_SET_VALUE Developed > Matured
    -> Edit_Attribute
Edit_Attribute: AttributeValueMapper
    DIRECTION = Forward (Source To Destination)
    LUT:
      Baby blue
      ,Baby_blue,Amaranth,Amaranth,Amber,Amber,Ametheyst,Ametheyst,Apricot,Apricot,Aquamarine,Aquamarine,Beige,Beige,Black,Black,Blue,Blue,Blue_green,Blue_green,Blue_violet,Blue_violet,Blush,Blush,Bronze,Bronze,Brown,Brown,Burgundy,Burgundy,Byzantium,Byzantium,Carmine,Carmine,Cerise,Cerise,Cerulean,Cerulean,Champagne,Champagne,Chartreuse_green,Chartreuse_green,Chocolate,Chocolate,Cobalt_blue,Cobalt_blue,Coffee,Coffee,Copper,Copper,Coral,Coral,Crimson,Crimson,Cyan,Cyan,Dessert_sand,Dessert_sand,Electric_blue,Electric_blue,Emerald,Emerald,Erin,Erin,Gold,Gold,Gray,Gray,Green,Green,Harlequin,Harlequin,Indigo,Indigo,Ivory,Ivory,Jade,Jade,Jungle_green,Jungle_green,Lavender,Lavender,Lemon,Lemon,Lilac,Lilac,Lime,Lime,Magenta,Magenta,Magenta_rose,Magenta_rose,Maroon,Maroon,Mauve,Mauve,Navy_blue,Navy_blue,Ochre,Ochre,Olive,Olive,Orange,Orange,Orange_red,Orange_red,Orchid,Orchid,Peach,Peach,Pear,Pear,Periwinkle,Periwinkle,Pink,Pink,Plum,Plum,Puce,Puce,Purple,Purple,Raspberry,Raspberry,Red,Red,Rose,Rose,Ruby,Ruby,Salmon,Salmon,Sangria,Sangria,Sapphire,Sapphire,Scarlet,Scarlet,Silver,Silver,Slate_gray,Slate_gray,Spring_bud,Spring_bud,Tan,Tan,Taupe,Taupe,Teal,Teal,Turquoise,Turquoise,Ultramarine,Ultramarine,Violet,Violet,Viridian,Viridian,White,White,Yellow,Yellow
    SRC = Flower_colour
    VAL_ATTR = Flower_Color
    -> Create_Date_n_Code
Create_Date_n_Code: AttributeCreator
    ATTR_TABLE:
      SET_TO Date = @Value(Year)/@Value(Month)/@Value(Day)
      SET_TO Code = @Left(@Value(Key),2)@UpperCase(@Right(@Value(Flower_Color),1))
    -> Arrange_Attributes
Arrange_Attributes: AttributeManager
    ATTR_TABLE:
      RENAME_SET_VALUE Flower_Color > Flo_Color
      REMOVE Key
      REMOVE Flower_colour
      RENAME_SET_VALUE Flower_Count > Flo_Count
      RENAME_SET_VALUE Flower_Shape > Flo_Shape
    -> Flower (writer SHAPEFILE_1)
Flower (writer SHAPEFILE_1)
    attributes: Code char(200), Flo_Color char(254), Flo_Count number(11,0), Flo_Shape char(254), Matured char(254), Date char(200), Year char(200), Month char(200), Day char(200), Location char(254), Latitude double, Longitude double
