FME workspace Join_districts_to_flower_data.fmw

Parameters:
- SourceDataset_SHAPEFILE = /home/gift/Documents/git_projects/fme/fme_flower_analysis/output_shapefiles/Districts_SH.shp   # Source Esri Shapefile(s)
- DestDataset_SHAPEFILE = /home/gift/Documents/git_projects/fme/fme_flower_analysis/Flower_Dataset   # Destination Esri Shapefile Folder
- SourceDataset_SHAPEFILE_3 = /home/gift/Documents/git_projects/fme/fme_flower_analysis/output_shapefiles/Flower.shp   # Source Esri Shapefile(s)

Readers:
- SHAPEFILE_1: SHAPEFILE from $(SourceDataset_SHAPEFILE)
- SHAPEFILE_2: SHAPEFILE from $(SourceDataset_SHAPEFILE_3)

Writers:
- SHAPEFILE_3: SHAPEFILE to $(DestDataset_SHAPEFILE)

Districts_SH (reader SHAPEFILE_1)
    attributes: District char(50), SHAPE_LENG double, SHAPE_AREA double, State char(50)
    -> SpatialRelator [Supplier]
Flower (reader SHAPEFILE_2)
    attributes: Code char(200), Flo_Color char(254), Flo_Count number(11,0), Flo_Shape char(254), Matured char(254), Date char(200), Year char(200), Month char(200), Day char(200), Location char(254), Latitude double, Longitude double
    -> SpatialRelator [Requestor]
SpatialRelator
    AGGREGATE_HANDLING = Yes
    ATTR_ACCUM_MODE = Merge Supplier
    ATTR_CONFLICT_RES = Use Requestor
    CALC_CARD = No
    CURVE_BOUNDARY_RULE_PARAM = Default Rule
    LIST_ATTRS_TO_INCLUDE = District
    LIST_NAME = _relationships
    PREDICATES = INTERSECTS
    SUCCESS_ATTR = _related_candidates
    -> AttributeManager
AttributeManager
    ATTR_TABLE:
      REMOVE SHAPE_LENG
      REMOVE SHAPE_AREA
      REMOVE State
      REMOVE _relationships{}.District
      REMOVE _relationships{}.de9im
      REMOVE _relationships{}.pass{}
      REMOVE _related_candidates
    -> Flower_Dataset (writer SHAPEFILE_3)
Flower_Dataset (writer SHAPEFILE_3)
    attributes: Code char(200), Flo_Color char(254), Flo_Count number(11,0), Flo_Shape char(254), Matured char(254), District char(50), Date char(200), Year char(200), Month char(200), Day char(200), Location char(254), Latitude double, Longitude double
