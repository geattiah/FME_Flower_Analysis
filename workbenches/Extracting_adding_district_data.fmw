FME workspace Extracting_adding_district_data.fmw

Parameters:
- DestDataset_SHAPEFILE_2 = /home/gift/Documents/git_projects/fme/fme_flower_analysis/output_shapefiles   # Destination Esri Shapefile Folder
- SourceDataset_SHAPEFILE = /home/gift/Documents/git_projects/fme/fme_flower_analysis/shapefiles_Data/Germany_states.shp   # Source Esri Shapefile(s)
- DestDataset_SHAPEFILE = /home/gift/Documents/git_projects/fme/fme_flower_analysis/output_shapefiles   # Destination Esri Shapefile Folder
- DestDataset_SHAPEFILE_3 = /home/gift/Documents/git_projects/fme/fme_flower_analysis/output_shapefiles   # Destination Esri Shapefile Folder
- SourceDataset_SHAPEFILE_5 = /home/gift/Documents/git_projects/fme/fme_flower_analysis/output_shapefiles/schleswig_holstein.shp   # Source Esri Shapefile(s)
- SourceDataset_SHAPEFILE_4 = /home/gift/Documents/git_projects/fme/fme_flower_analysis/shapefiles_Data/Germany_district.shp   # Source Esri Shapefile(s)

Readers:
- SHAPEFILE_3: SHAPEFILE from $(SourceDataset_SHAPEFILE)
- SHAPEFILE_1: SHAPEFILE from $(SourceDataset_SHAPEFILE_5)
- SHAPEFILE_2: SHAPEFILE from $(SourceDataset_SHAPEFILE_4)

Writers:
- SHAPEFILE_5: SHAPEFILE to $(DestDataset_SHAPEFILE_2)
- SHAPEFILE_4: SHAPEFILE to $(DestDataset_SHAPEFILE)
- SHAPEFILE_6: SHAPEFILE to $(DestDataset_SHAPEFILE_3)

Germany_states (reader SHAPEFILE_3)
    attributes: USE long, RS char(2), RS_ALT char(12), GEN char(50), SHAPE_LENG double, SHAPE_AREA double
    -> AttributeFilter
AttributeFilter
    ATTR_NAME = GEN
    ATTR_VALUES = <Empty>,<Missing>,<Null>,<Unfiltered>,Baden-W�rttemberg,Bayern,Berlin,Brandenburg,Bremen,Hamburg,Hessen,Mecklenburg-Vorpommern,Niedersachsen,Nordrhein-Westfalen,Rheinland-Pfalz,Saarland,Sachsen,Sachsen-Anhalt,Schleswig-Holstein,Th�ringen
    Schleswig-Holstein -> schleswig_holstein (writer SHAPEFILE_6)
schleswig_holstein (writer SHAPEFILE_6)
    attributes: USE number(11,0), RS char(2), RS_ALT char(12), GEN char(50), SHAPE_LENG double, SHAPE_AREA double
Germany_district (reader SHAPEFILE_2)
    attributes: USE long, RS char(5), RS_ALT char(12), GEN char(50), SHAPE_LENG double, SHAPE_AREA double
    -> AttributeManager
AttributeManager
    ATTR_TABLE = RENAME_SET_VALUE GEN > Kreise
    -> SpatialRelator [Requestor]
schleswig_holstein (reader SHAPEFILE_1)
    attributes: USE number(11,0), RS char(2), RS_ALT char(12), GEN char(50), SHAPE_LENG double, SHAPE_AREA double
    -> SpatialRelator [Supplier]
SpatialRelator
    AGGREGATE_HANDLING = Yes
    ATTR_ACCUM_MODE = Merge Supplier
    ATTR_CONFLICT_RES = Use Requestor
    CALC_CARD = Yes
    CURVE_BOUNDARY_RULE_PARAM = Default Rule
    LIST_NAME = _relationships
    PREDICATES = INTERSECTS
    SUCCESS_ATTR = _related_candidates
    -> AttributeFilter_2
AttributeFilter_2
    ATTR_NAME = _relationships{0}.GEN
    ATTR_VALUES = <Empty>,<Missing>,<Null>,<Unfiltered>
    <UNFILTERED> -> AttributeCreator
AttributeCreator
    ATTR_TABLE = SET_TO Kreise = @Value(Kreise)
    -> AttributeManager_2
AttributeManager_2
    ATTR_TABLE:
      RENAME_SET_VALUE Kreise > District
      REMOVE USE
      REMOVE RS
      REMOVE RS_ALT
      RENAME_SET_VALUE GEN > State
      REMOVE _relationships{}.USE
      REMOVE _relationships{}.RS
      REMOVE _relationships{}.RS_ALT
      REMOVE _relationships{}.GEN
      REMOVE _relationships{}.SHAPE_LENG
      REMOVE _relationships{}.SHAPE_AREA
      REMOVE _relationships{}.de9im
      REMOVE _relationships{}.pass{}
      REMOVE _relationships{}.card_point
      REMOVE _relationships{}.card_line
      REMOVE _relationships{}.card_area
      REMOVE _related_candidates
    -> Districts_SH (writer SHAPEFILE_5)
Districts_SH (writer SHAPEFILE_5)
    attributes: District char(50), SHAPE_LENG double, SHAPE_AREA double, State char(50)
