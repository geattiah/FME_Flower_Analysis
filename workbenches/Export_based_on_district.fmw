FME workspace Export_based_on_district.fmw

Parameters:
- SourceDataset_SHAPEFILE = /home/gift/Documents/Flower_Dataset/Flower_Dataset.shp   # Source Esri Shapefile(s)
- DestDataset_SHAPEFILE = /home/gift/Documents/git_projects/fme/FME_Flower_Analysis/output_shapefiles_by_district   # Destination Esri Shapefile Folder
- DestDataset_SHAPEFILE_34 = /home/gift/Documents/git_projects/fme/FME_Flower_Analysis/output_shapefiles_by_district   # Destination Esri Shapefile Folder
- DestDataset_SHAPEFILE_26 = /home/gift/Documents/git_projects/fme/FME_Flower_Analysis/output_shapefiles_by_district   # Destination Esri Shapefile Folder
- DestDataset_SHAPEFILE_22 = /home/gift/Documents/git_projects/fme/FME_Flower_Analysis/output_shapefiles_by_district   # Destination Esri Shapefile Folder
- DestDataset_SHAPEFILE_30 = /home/gift/Documents/git_projects/fme/FME_Flower_Analysis/output_shapefiles_by_district   # Destination Esri Shapefile Folder
- DestDataset_SHAPEFILE_38 = /home/gift/Documents/git_projects/fme/FME_Flower_Analysis/output_shapefiles_by_district   # Destination Esri Shapefile Folder
- DestDataset_SHAPEFILE_24 = /home/gift/Documents/git_projects/fme/FME_Flower_Analysis/output_shapefiles_by_district   # Destination Esri Shapefile Folder
- DestDataset_SHAPEFILE_28 = /home/gift/Documents/git_projects/fme/FME_Flower_Analysis/output_shapefiles_by_district   # Destination Esri Shapefile Folder
- DestDataset_SHAPEFILE_32 = /home/gift/Documents/git_projects/fme/FME_Flower_Analysis/output_shapefiles_by_district   # Destination Esri Shapefile Folder
- DestDataset_SHAPEFILE_36 = /home/gift/Documents/git_projects/fme/FME_Flower_Analysis/output_shapefiles_by_district   # Destination Esri Shapefile Folder
- DestDataset_SHAPEFILE_40 = /home/gift/Documents/git_projects/fme/FME_Flower_Analysis/output_shapefiles_by_district   # Destination Esri Shapefile Folder
- DestDataset_SHAPEFILE_23 = /home/gift/Documents/git_projects/fme/FME_Flower_Analysis/output_shapefiles_by_district   # Destination Esri Shapefile Folder
- DestDataset_SHAPEFILE_25 = /home/gift/Documents/git_projects/fme/FME_Flower_Analysis/output_shapefiles_by_district   # Destination Esri Shapefile Folder
- DestDataset_SHAPEFILE_27 = /home/gift/Documents/git_projects/fme/FME_Flower_Analysis/output_shapefiles_by_district   # Destination Esri Shapefile Folder
- DestDataset_SHAPEFILE_29 = /home/gift/Documents/git_projects/fme/FME_Flower_Analysis/output_shapefiles_by_district   # Destination Esri Shapefile Folder
- DestDataset_SHAPEFILE_31 = /home/gift/Documents/git_projects/fme/FME_Flower_Analysis/output_shapefiles_by_district   # Destination Esri Shapefile Folder
- DestDataset_SHAPEFILE_33 = /home/gift/Documents/git_projects/fme/FME_Flower_Analysis/output_shapefiles_by_district   # Destination Esri Shapefile Folder
- DestDataset_SHAPEFILE_35 = /home/gift/Documents/git_projects/fme/FME_Flower_Analysis/output_shapefiles_by_district   # Destination Esri Shapefile Folder
- DestDataset_SHAPEFILE_37 = /home/gift/Documents/git_projects/fme/FME_Flower_Analysis/output_shapefiles_by_district   # Destination Esri Shapefile Folder
- DestDataset_SHAPEFILE_39 = /home/gift/Documents/git_projects/fme/FME_Flower_Analysis/output_shapefiles_by_district   # Destination Esri Shapefile Folder

Readers:
- SHAPEFILE_1: SHAPEFILE from $(SourceDataset_SHAPEFILE)

Writers:
- SHAPEFILE_2: SHAPEFILE to $(DestDataset_SHAPEFILE)
- SHAPEFILE_3: SHAPEFILE to $(DestDataset_SHAPEFILE_34)
- SHAPEFILE_4: SHAPEFILE to $(DestDataset_SHAPEFILE_26)
- SHAPEFILE_5: SHAPEFILE to $(DestDataset_SHAPEFILE_22)
- SHAPEFILE_6: SHAPEFILE to $(DestDataset_SHAPEFILE_30)
- SHAPEFILE_7: SHAPEFILE to $(DestDataset_SHAPEFILE_38)
- SHAPEFILE_8: SHAPEFILE to $(DestDataset_SHAPEFILE_24)
- SHAPEFILE_9: SHAPEFILE to $(DestDataset_SHAPEFILE_28)
- SHAPEFILE_10: SHAPEFILE to $(DestDataset_SHAPEFILE_32)
- SHAPEFILE_11: SHAPEFILE to $(DestDataset_SHAPEFILE_36)
- SHAPEFILE_12: SHAPEFILE to $(DestDataset_SHAPEFILE_40)
- SHAPEFILE_13: SHAPEFILE to $(DestDataset_SHAPEFILE_23)
- SHAPEFILE_14: SHAPEFILE to $(DestDataset_SHAPEFILE_25)
- SHAPEFILE_15: SHAPEFILE to $(DestDataset_SHAPEFILE_27)
- SHAPEFILE_16: SHAPEFILE to $(DestDataset_SHAPEFILE_29)
- SHAPEFILE_17: SHAPEFILE to $(DestDataset_SHAPEFILE_31)
- SHAPEFILE_18: SHAPEFILE to $(DestDataset_SHAPEFILE_33)
- SHAPEFILE_19: SHAPEFILE to $(DestDataset_SHAPEFILE_35)
- SHAPEFILE_20: SHAPEFILE to $(DestDataset_SHAPEFILE_37)
- SHAPEFILE_21: SHAPEFILE to $(DestDataset_SHAPEFILE_39)

Flower_Dataset (reader SHAPEFILE_1)
    attributes: Code char(200), Flo_Color char(254), Flo_Count number(11,0), Flo_Shape char(254), Matured char(254), District char(50), Date char(200), Year char(200), Month char(200), Day char(200), Location char(254), Latitude double, Longitude double
    -> AttributeFilter
AttributeFilter
    ATTR_NAME = District
    ATTR_VALUES = <Empty>,<Missing>,<Null>,<Unfiltered>,Herzogtum Lauenburg,Dithmarschen,Flensburg,Hamburg,Kiel,Ludwigslust-Parchim,Luebeck,Lueneburg,Neumuenster,Nordfriesland,Nordwestmecklenburg,Ostholstein,Pinneberg,Ploen,Rendsburg-Eckernfoerde,Schleswig-Flensburg,Segeberg,Steinburg,Stormarn
    <EMPTY> -> Junction
    <MISSING> -> AttributeManager
    <NULL> -> Junction
    <UNFILTERED> -> Junction
    Herzogtum Lauenburg -> Junction
    Dithmarschen -> Junction
    Flensburg -> Junction
    Hamburg -> Junction
    Kiel -> Junction
    Ludwigslust-Parchim -> Junction
    Luebeck -> Junction
    Lueneburg -> Junction
    Neumuenster -> Junction
    Nordfriesland -> Junction
    Nordwestmecklenburg -> Junction
    Ostholstein -> Junction
    Pinneberg -> Junction
    Ploen -> Junction
    Rendsburg-Eckernfoerde -> Junction
    Schleswig-Flensburg -> Junction
    Segeberg -> Junction
    Steinburg -> Junction
    Stormarn -> Junction
AttributeManager
    ATTR_TABLE = SET_TO District = None
    -> Junction
Junction
    -> AttributeFilter_2
AttributeFilter_2
    ATTR_NAME = District
    ATTR_VALUES = <Empty>,<Missing>,<Null>,<Unfiltered>,Herzogtum Lauenburg,Dithmarschen,Flensburg,Hamburg,Kiel,Ludwigslust-Parchim,Luebeck,Lueneburg,Neumuenster,Nordfriesland,Nordwestmecklenburg,Ostholstein,Pinneberg,Ploen,Rendsburg-Eckernfoerde,Schleswig-Flensburg,Segeberg,Steinburg,Stormarn
    <UNFILTERED> -> None (writer SHAPEFILE_21)
    Herzogtum Lauenburg -> Herzogtum Lauenburg (writer SHAPEFILE_20)
    Dithmarschen -> Dithmarschen (writer SHAPEFILE_19)
    Flensburg -> Flensburg (writer SHAPEFILE_18)
    Hamburg -> Hamburg (writer SHAPEFILE_17)
    Kiel -> Kiel (writer SHAPEFILE_16)
    Ludwigslust-Parchim -> Ludwigslust-Parchim (writer SHAPEFILE_15)
    Luebeck -> Luebeck (writer SHAPEFILE_14)
    Lueneburg -> Lueneburg (writer SHAPEFILE_13)
    Neumuenster -> Neumuenster (writer SHAPEFILE_12)
    Nordfriesland -> Nordfriesland (writer SHAPEFILE_11)
    Nordwestmecklenburg -> Nordwestmecklenburg (writer SHAPEFILE_10)
    Ostholstein -> Ostholstein (writer SHAPEFILE_9)
    Pinneberg -> Pinneberg (writer SHAPEFILE_8)
    Ploen -> Ploen (writer SHAPEFILE_2)
    Rendsburg-Eckernfoerde -> Rendsburg-Eckernfoerde (writer SHAPEFILE_7)
    Schleswig-Flensburg -> Schleswig-Flensburg (writer SHAPEFILE_6)
    Segeberg -> Segeberg (writer SHAPEFILE_5)
    Steinburg -> Steinburg (writer SHAPEFILE_4)
    Stormarn -> Stormarn (writer SHAPEFILE_3)
None (writer SHAPEFILE_21)
    attributes: Code char(200), Flo_Color char(254), Flo_Count number(11,0), Flo_Shape char(254), Matured char(254), District char(50), Date char(200), Year char(200), Month char(200), Day char(200), Location char(254), Latitude double, Longitude double
Herzogtum Lauenburg (writer SHAPEFILE_20)
    attributes: Code char(200), Flo_Color char(254), Flo_Count number(11,0), Flo_Shape char(254), Matured char(254), District char(50), Date char(200), Year char(200), Month char(200), Day char(200), Location char(254), Latitude double, Longitude double
Dithmarschen (writer SHAPEFILE_19)
    attributes: Code char(200), Flo_Color char(254), Flo_Count number(11,0), Flo_Shape char(254), Matured char(254), District char(50), Date char(200), Year char(200), Month char(200), Day char(200), Location char(254), Latitude double, Longitude double
Flensburg (writer SHAPEFILE_18)
    attributes: Code char(200), Flo_Color char(254), Flo_Count number(11,0), Flo_Shape char(254), Matured char(254), District char(50), Date char(200), Year char(200), Month char(200), Day char(200), Location char(254), Latitude double, Longitude double
Hamburg (writer SHAPEFILE_17)
    attributes: Code char(200), Flo_Color char(254), Flo_Count number(11,0), Flo_Shape char(254), Matured char(254), District char(50), Date char(200), Year char(200), Month char(200), Day char(200), Location char(254), Latitude double, Longitude double
Kiel (writer SHAPEFILE_16)
    attributes: Code char(200), Flo_Color char(254), Flo_Count number(11,0), Flo_Shape char(254), Matured char(254), District char(50), Date char(200), Year char(200), Month char(200), Day char(200), Location char(254), Latitude double, Longitude double
Ludwigslust-Parchim (writer SHAPEFILE_15)
    attributes: Code char(200), Flo_Color char(254), Flo_Count number(11,0), Flo_Shape char(254), Matured char(254), District char(50), Date char(200), Year char(200), Month char(200), Day char(200), Location char(254), Latitude double, Longitude double
Luebeck (writer SHAPEFILE_14)
    attributes: Code char(200), Flo_Color char(254), Flo_Count number(11,0), Flo_Shape char(254), Matured char(254), District char(50), Date char(200), Year char(200), Month char(200), Day char(200), Location char(254), Latitude double, Longitude double
Lueneburg (writer SHAPEFILE_13)
    attributes: Code char(200), Flo_Color char(254), Flo_Count number(11,0), Flo_Shape char(254), Matured char(254), District char(50), Date char(200), Year char(200), Month char(200), Day char(200), Location char(254), Latitude double, Longitude double
Neumuenster (writer SHAPEFILE_12)
    attributes: Code char(200), Flo_Color char(254), Flo_Count number(11,0), Flo_Shape char(254), Matured char(254), District char(50), Date char(200), Year char(200), Month char(200), Day char(200), Location char(254), Latitude double, Longitude double
Nordfriesland (writer SHAPEFILE_11)
    attributes: Code char(200), Flo_Color char(254), Flo_Count number(11,0), Flo_Shape char(254), Matured char(254), District char(50), Date char(200), Year char(200), Month char(200), Day char(200), Location char(254), Latitude double, Longitude double
Nordwestmecklenburg (writer SHAPEFILE_10)
    attributes: Code char(200), Flo_Color char(254), Flo_Count number(11,0), Flo_Shape char(254), Matured char(254), District char(50), Date char(200), Year char(200), Month char(200), Day char(200), Location char(254), Latitude double, Longitude double
Ostholstein (writer SHAPEFILE_9)
    attributes: Code char(200), Flo_Color char(254), Flo_Count number(11,0), Flo_Shape char(254), Matured char(254), District char(50), Date char(200), Year char(200), Month char(200), Day char(200), Location char(254), Latitude double, Longitude double
Pinneberg (writer SHAPEFILE_8)
    attributes: Code char(200), Flo_Color char(254), Flo_Count number(11,0), Flo_Shape char(254), Matured char(254), District char(50), Date char(200), Year char(200), Month char(200), Day char(200), Location char(254), Latitude double, Longitude double
Ploen (writer SHAPEFILE_2)
    attributes: Code char(200), Flo_Color char(254), Flo_Count number(11,0), Flo_Shape char(254), Matured char(254), District char(50), Date char(200), Year char(200), Month char(200), Day char(200), Location char(254), Latitude double, Longitude double
Rendsburg-Eckernfoerde (writer SHAPEFILE_7)
    attributes: Code char(200), Flo_Color char(254), Flo_Count number(11,0), Flo_Shape char(254), Matured char(254), District char(50), Date char(200), Year char(200), Month char(200), Day char(200), Location char(254), Latitude double, Longitude double
Schleswig-Flensburg (writer SHAPEFILE_6)
    attributes: Code char(200), Flo_Color char(254), Flo_Count number(11,0), Flo_Shape char(254), Matured char(254), District char(50), Date char(200), Year char(200), Month char(200), Day char(200), Location char(254), Latitude double, Longitude double
Segeberg (writer SHAPEFILE_5)
    attributes: Code char(200), Flo_Color char(254), Flo_Count number(11,0), Flo_Shape char(254), Matured char(254), District char(50), Date char(200), Year char(200), Month char(200), Day char(200), Location char(254), Latitude double, Longitude double
Steinburg (writer SHAPEFILE_4)
    attributes: Code char(200), Flo_Color char(254), Flo_Count number(11,0), Flo_Shape char(254), Matured char(254), District char(50), Date char(200), Year char(200), Month char(200), Day char(200), Location char(254), Latitude double, Longitude double
Stormarn (writer SHAPEFILE_3)
    attributes: Code char(200), Flo_Color char(254), Flo_Count number(11,0), Flo_Shape char(254), Matured char(254), District char(50), Date char(200), Year char(200), Month char(200), Day char(200), Location char(254), Latitude double, Longitude double
