FME workspace Replace_missen_values.fmw

Parameters:
- SourceDataset_SHAPEFILE = /home/gift/Documents/Flower_Dataset/Flower_Dataset.shp   # Source Esri Shapefile(s)
- DestDataset_SHAPEFILE = /home/gift/Documents/Flower_Dataset/Flower_Final   # Destination Esri Shapefile Folder

Readers:
- SHAPEFILE_1: SHAPEFILE from $(SourceDataset_SHAPEFILE)

Writers:
- SHAPEFILE_2: SHAPEFILE to $(DestDataset_SHAPEFILE)

Flower_Dataset (reader SHAPEFILE_1)
    attributes: Code char(200), Flo_Color char(254), Flo_Count number(11,0), Flo_Shape char(254), Matured char(254), District char(50), Date char(200), Year char(200), Month char(200), Day char(200), Location char(254), Latitude double, Longitude double
    -> AttributeFilter
AttributeFilter
    ATTR_NAME = District
    ATTR_VALUES = <Empty>,<Missing>,<Null>,<Unfiltered>,Herzogtum Lauenburg,Dithmarschen,Flensburg,Hamburg,Kiel,Ludwigslust-Parchim,Luebeck,Lueneburg,Neumuenster,Nordfriesland,Nordwestmecklenburg,Ostholstein,Pinneberg,Ploen,Rendsburg-Eckernfoerde,Schleswig-Flensburg,Segeberg,Steinburg,Stormarn
    <EMPTY> -> Junction
    <MISSING> -> AttributeManager
    <NULL> -> Junction
    <UNFILTERED> -> Junction
    Herzogtum Lauenburg -> Junction
    Dithmarschen -> Junction
    Flensburg -> Junction
    Hamburg -> Junction
    Kiel -> Junction
    Ludwigslust-Parchim -> Junction
    Luebeck -> Junction
    Lueneburg -> Junction
    Neumuenster -> Junction
    Nordfriesland -> Junction
    Nordwestmecklenburg -> Junction
    Ostholstein -> Junction
    Pinneberg -> Junction
    Ploen -> Junction
    Rendsburg-Eckernfoerde -> Junction
    Schleswig-Flensburg -> Junction
    Segeberg -> Junction
    Steinburg -> Junction
    Stormarn -> Junction
AttributeManager
    ATTR_TABLE = SET_TO District = Outside
    -> Junction
Junction
    -> Flower_Data_final (writer SHAPEFILE_2)
Flower_Data_final (writer SHAPEFILE_2)
    attributes: Code char(200), Flo_Color char(254), Flo_Count number(11,0), Flo_Shape char(254), Matured char(254), District char(50), Date char(200), Year char(200), Month char(200), Day char(200), Location char(254), Latitude double, Longitude double
