FME workspace Transform_data.fmw

Parameters:
- SourceDataset_SHAPEFILE = /home/gift/Documents/FME/Or_project/Flower.shp   # Source Esri Shapefile(s)
- DestDataset_SHAPEFILE = /home/gift/Documents/FME/Or_project   # Destination Esri Shapefile Folder
- SourceDataset_SHAPEFILE_2 = /home/gift/Documents/FME/Or_project/Flow_mod.shp   # Source Esri Shapefile(s)
- DestDataset_SHAPEFILE_3 = /home/gift/Documents/FME/Or_project   # Destination Esri Shapefile Folder
- SourceDataset_SHAPEFILE_4 = /home/gift/Documents/FME/Or_project/Flower_1.shp   # Source Esri Shapefile(s)
- DestDataset_SHAPEFILE_5 = /home/gift/Documents/FME/Or_project   # Destination Esri Shapefile Folder
- SourceDataset_SHAPEFILE_6 = /home/gift/Documents/FME/Or_project/Flower_2.shp   # Source Esri Shapefile(s)
- DestDataset_SHAPEFILE_7 = /home/gift/Documents/FME/Or_project   # Destination Esri Shapefile Folder
- SourceDataset_SHAPEFILE_8 = /home/gift/Documents/FME/Or_project/Flower_3.shp   # Source Esri Shapefile(s)
- DestDataset_SHAPEFILE_9 = /home/gift/Documents/FME/Flower_Project   # Destination Esri Shapefile Folder

Readers:
- SHAPEFILE_1: SHAPEFILE from $(SourceDataset_SHAPEFILE)
- SHAPEFILE_3: SHAPEFILE from $(SourceDataset_SHAPEFILE_2)
- SHAPEFILE_5: SHAPEFILE from $(SourceDataset_SHAPEFILE_4)
- SHAPEFILE_7: SHAPEFILE from $(SourceDataset_SHAPEFILE_6)
- SHAPEFILE_9: SHAPEFILE from $(SourceDataset_SHAPEFILE_8)

Writers:
- SHAPEFILE_2: SHAPEFILE to $(DestDataset_SHAPEFILE)
- SHAPEFILE_4: SHAPEFILE to $(DestDataset_SHAPEFILE_3)
- SHAPEFILE_6: SHAPEFILE to $(DestDataset_SHAPEFILE_5)
- SHAPEFILE_8: SHAPEFILE to $(DestDataset_SHAPEFILE_7)
- SHAPEFILE_10: SHAPEFILE to $(DestDataset_SHAPEFILE_9)

Flower_2 (reader SHAPEFILE_7)
    attributes: Flower_Col char(254), Total_Coun number(11,0), Vitality char(254), Properties char(254), Date date, Type char(254), Code char(254), Latitude double, Longitude double, Precision char(254), Known char(254), Flower char(254), Shape char(254)
    -> AttributeManager_2
AttributeManager_2
    ATTR_TABLE = SET_TO Key
    -> AttributeCreator
AttributeCreator
    ATTR_TABLE = SET_TO Key = @UpperCase(@Left(@Value(Flower),3))
    -> AttributeCreator_2
AttributeCreator_2
    ATTR_TABLE = SET_TO Year = @Left(@Value(Date),4)
    -> AttributeCreator_3
AttributeCreator_3
    ATTR_TABLE = SET_TO Day = @Right(@Value(Date),2)
    -> AttributeCreator_4
AttributeCreator_4
    ATTR_TABLE = SET_TO Month = @Left(@Right(@Value(Date),4),2)
    -> AttributeFilter_3
AttributeFilter_3
    ATTR_NAME = Precision
    ATTR_VALUES = <Empty>,<Missing>,<Null>,<Unfiltered>,Exakte Lokalisierung,Mittelpunkt der Gemeinde,exakte Lokalisierung (Polygon),Halbminutenfeld,Ort,Polygon
    <EMPTY> -> Junction_3
    <MISSING> -> Junction_3
    <NULL> -> Junction_3
    <UNFILTERED> -> Junction_3
    Exakte Lokalisierung -> Junction_3
    Mittelpunkt der Gemeinde -> Junction_3
    exakte Lokalisierung (Polygon) -> Junction_3
    Halbminutenfeld -> Junction_3
    Ort -> Junction_3
    Polygon -> Junction_3
Junction_3
    -> AttributeValueMapper_3
AttributeValueMapper_3
    DIRECTION = Forward (Source To Destination)
    LUT = Exakte Lokalisierung,Exact_location,Mittelpunkt der Gemeinde,Middle_of_group,exakte Lokalisierung (Polygon),Exact_location_group,Halbminutenfeld,Half_minute_away,Ort,Town_point,Polygon,Group
    SRC = Precision
    VAL_ATTR = Precise
    -> AttributeFilter_4
AttributeFilter_4
    ATTR_NAME = Known
    ATTR_VALUES = <Empty>,<Missing>,<Null>,<Unfiltered>,Ja,Nein
    <EMPTY> -> Junction_4
    <MISSING> -> Junction_4
    <NULL> -> Junction_4
    <UNFILTERED> -> Junction_4
    Ja -> Junction_4
    Nein -> Junction_4
Junction_4
    -> AttributeValueMapper_4
AttributeValueMapper_4
    DIRECTION = Forward (Source To Destination)
    LUT = Ja,Yes,Nein,No
    SRC = Known
    VAL_ATTR = Developed
    -> Flower_3 (writer SHAPEFILE_8)
Flower_3 (writer SHAPEFILE_8)
    attributes: Month char(200), Day char(200), Year char(200), Key char(200), Flower_Col char(254), Total_Coun number(11,0), Vitality char(254), Properties char(254), Date date, Type char(254), Code char(254), Latitude double, Longitude double, Precision char(254), Known char(254), Flower char(254), Shape char(254), Precise char(254), Developed char(254)
Flower (reader SHAPEFILE_1)
    attributes: Flower_Col char(254), Total_Coun number(11,0), Vitality char(254), Properties char(254), Date date, Type char(254), Code char(254), Latitude double, Longitude double, Precision char(254), Known char(254)
    -> AttributeFilter
AttributeFilter
    ATTR_NAME = Flower_Col
    ATTR_VALUES = Bluthänfling (Hänfling),Gebirgsstelze (Bergstelze),Großer Brachvogel,Schafstelze (flava), Wiesenschafstelze,Bartmeise,Baumfalke,Bekassine,Bergente,Beutelmeise,Blaukehlchen,Brandseeschwalbe,Braunkehlchen,Drosselrohrsänger,Eiderente,Eisvogel,Feldlerche,Fichtenkreuzschnabel,Fischadler,Goldammer,Grauammer,Grünspecht,Gänsesäger,Heidelerche,Kampfläufer,Karmingimpel,Kiebitz,Knäkente,Kolbenente,Kornweihe,Kranich,Lachseeschwalbe,Löffler,Mantelmöwe,Mittelmeermöwe,Mittelspecht,Mittelsäger,Nachtigall,Nebelkrähe,Neuntöter,Ortolan,Pfeifente,Pirol,Raubwürger,Raufußkauz,Rebhuhn,Rohrdommel,Rohrschwirl,Rotmilan,Rotschenkel,Sandregenpfeifer,Schilfrohrsänger,Schlagschwirl,Schwarzhalstaucher,Schwarzkehlchen,Schwarzkopfmöwe,Schwarzmilan,Schwarzstorch,Seeadler,Seeregenpfeifer,Sperbergrasmücke,Spießente,Steinkauz,Steinschmätzer,Sturmmöwe,Sumpfohreule,Trauerseeschwalbe,Tüpfelsumpfhuhn,Uferschnepfe,Uhu,Wacholderdrossel,Wachtel,Wachtelkönig,Waldwasserläufer,Wanderfalke,Weißstorch,Wendehals,Wiesenpieper,Wiesenweihe,Ziegenmelker,Zwergschnäpper,Zwergseeschwalbe
    <EMPTY> -> Junction
    <MISSING> -> Junction
    <NULL> -> Junction
    <UNFILTERED> -> Junction
    Bluthänfling (Hänfling) -> Junction
    Gebirgsstelze (Bergstelze) -> Junction
    Großer Brachvogel -> Junction
    Schafstelze (flava), Wiesenschafstelze -> Junction
    Bartmeise -> Junction
    Baumfalke -> Junction
    Bekassine -> Junction
    Bergente -> Junction
    Beutelmeise -> Junction
    Blaukehlchen -> Junction
    Brandseeschwalbe -> Junction
    Braunkehlchen -> Junction
    Drosselrohrsänger -> Junction
    Eiderente -> Junction
    Eisvogel -> Junction
    Feldlerche -> Junction
    Fichtenkreuzschnabel -> Junction
    Fischadler -> Junction
    Goldammer -> Junction
    Grauammer -> Junction
    Grünspecht -> Junction
    Gänsesäger -> Junction
    Heidelerche -> Junction
    Kampfläufer -> Junction
    Karmingimpel -> Junction
    Kiebitz -> Junction
    Knäkente -> Junction
    Kolbenente -> Junction
    Kornweihe -> Junction
    Kranich -> Junction
    Lachseeschwalbe -> Junction
    Löffler -> Junction
    Mantelmöwe -> Junction
    Mittelmeermöwe -> Junction
    Mittelspecht -> Junction
    Mittelsäger -> Junction
    Nachtigall -> Junction
    Nebelkrähe -> Junction
    Neuntöter -> Junction
    Ortolan -> Junction
    Pfeifente -> Junction
    Pirol -> Junction
    Raubwürger -> Junction
    Raufußkauz -> Junction
    Rebhuhn -> Junction
    Rohrdommel -> Junction
    Rohrschwirl -> Junction
    Rotmilan -> Junction
    Rotschenkel -> Junction
    Sandregenpfeifer -> Junction
    Schilfrohrsänger -> Junction
    Schlagschwirl -> Junction
    Schwarzhalstaucher -> Junction
    Schwarzkehlchen -> Junction
    Schwarzkopfmöwe -> Junction
    Schwarzmilan -> Junction
    Schwarzstorch -> Junction
    Seeadler -> Junction
    Seeregenpfeifer -> Junction
    Sperbergrasmücke -> Junction
    Spießente -> Junction
    Steinkauz -> Junction
    Steinschmätzer -> Junction
    Sturmmöwe -> Junction
    Sumpfohreule -> Junction
    Trauerseeschwalbe -> Junction
    Tüpfelsumpfhuhn -> Junction
    Uferschnepfe -> Junction
    Uhu -> Junction
    Wacholderdrossel -> Junction
    Wachtel -> Junction
    Wachtelkönig -> Junction
    Waldwasserläufer -> Junction
    Wanderfalke -> Junction
    Weißstorch -> Junction
    Wendehals -> Junction
    Wiesenpieper -> Junction
    Wiesenweihe -> Junction
    Ziegenmelker -> Junction
    Zwergschnäpper -> Junction
    Zwergseeschwalbe -> Junction
Junction
    -> AttributeValueMapper
AttributeValueMapper
    DIRECTION = Forward (Source To Destination)
    LUT:
      Bluthänfling (Hänfling),Amaranth,Gebirgsstelze (Bergstelze),Amber,Großer Brachvogel,Ametheyst,Schafstelze (flava), Wiesenschafstelze,Apricot,Bartmeise,Aquamarine,Baumfalke,Baby blue
      ,Bekassine,Beige,Bergente,Black,Beutelmeise,Blue,Blaukehlchen,Blue_green,Brandseeschwalbe,Blue_violet,Braunkehlchen,Blush,Drosselrohrsänger,Bronze,Eiderente,Brown,Eisvogel,Burgundy,Feldlerche,Byzantium,Fichtenkreuzschnabel,Carmine,Fischadler,Cerise,Goldammer,Cerulean,Grauammer,Champagne,Grünspecht,Chartreuse_green,Gänsesäger,Chocolate,Heidelerche,Cobalt_blue,Kampfläufer,Coffee,Karmingimpel,Copper,Kiebitz,Coral,Knäkente,Crimson,Kolbenente,Cyan,Kornweihe,Dessert_sand,Kranich,Electric_blue,Lachseeschwalbe,Emerald,Löffler,Erin,Mantelmöwe,Gold,Mittelmeermöwe,Gray,Mittelspecht,Green,Mittelsäger,Harlequin,Nachtigall,Indigo,Nebelkrähe,Ivory,Neuntöter,Jade,Ortolan,Jungle_green,Pfeifente,Lavender,Pirol,Lemon,Raubwürger,Lilac,Raufußkauz,Lime,Rebhuhn,Magenta,Rohrdommel,Magenta_rose,Rohrschwirl,Maroon,Rotmilan,Mauve,Rotschenkel,Navy_blue,Sandregenpfeifer,Ochre,Schilfrohrsänger,Olive,Schlagschwirl,Orange,Schwarzhalstaucher,Orange_red,Schwarzkehlchen,Orchid,Schwarzkopfmöwe,Peach,Schwarzmilan,Pear,Schwarzstorch,Periwinkle,Seeadler,Tan,Seeregenpfeifer,Pink,Sperbergrasmücke,Plum,Spießente,Taupe,Steinkauz,Puce,Steinschmätzer,Purple,Sturmmöwe,Raspberry,Sumpfohreule,Red,Trauerseeschwalbe,Teal,Tüpfelsumpfhuhn,Rose,Uferschnepfe,Ruby,Uhu,Salmon,Wacholderdrossel,Sangria,Wachtel,Sapphire,Wachtelkönig,Scarlet,Waldwasserläufer,Silver,Wanderfalke,Turquoise,Weißstorch,Ultramarine,Wendehals,Violet,Wiesenpieper,Slate_gray,Wiesenweihe,Spring_bud,Ziegenmelker,Viridian,Zwergschnäpper,White,Zwergseeschwalbe,Yellow
    SRC = Flower_Col
    VAL_ATTR = _looked_up
    -> Flow_mod (writer SHAPEFILE_2)
Flow_mod (writer SHAPEFILE_2)
    attributes: Flower_Col char(254), Total_Coun number(11,0), Vitality char(254), Properties char(254), Date date, Type char(254), Code char(254), Latitude double, Longitude double, Precision char(254), Known char(254), _looked_up char(254)
Flow_mod (reader SHAPEFILE_3)
    attributes: Flower_Col char(254), Total_Coun number(11,0), Vitality char(254), Properties char(254), Date date, Type char(254), Code char(254), Latitude double, Longitude double, Precision char(254), Known char(254), _looked_up char(254)
    -> AttributeManager
AttributeManager
    ATTR_TABLE = RENAME_SET_VALUE _looked_up > Flower
    -> Flower_1 (writer SHAPEFILE_4)
Flower_1 (writer SHAPEFILE_4)
    attributes: Flower_Col char(254), Total_Coun number(11,0), Vitality char(254), Properties char(254), Date date, Type char(254), Code char(254), Latitude double, Longitude double, Precision char(254), Known char(254), Flower char(254)
Flower_1 (reader SHAPEFILE_5)
    attributes: Flower_Col char(254), Total_Coun number(11,0), Vitality char(254), Properties char(254), Date date, Type char(254), Code char(254), Latitude double, Longitude double, Precision char(254), Known char(254), Flower char(254)
    -> AttributeFilter_2
AttributeFilter_2
    ATTR_NAME = Vitality
    ATTR_VALUES = <Empty>,<Missing>,<Null>,<Unfiltered>,Fang zur Beringung,Flug zum / vom Schlafplatz,Gesang / Balz,N ziehend,NO ziehend,NW ziehend,Nahrung suchend,O ziehend,Revier (basierend auf mehreren Erfassungen),S ziehend,SO ziehend,SW ziehend,Schlaf- / Sammelplatz,Totfund / Rupfung,W ziehend,rastend / ruhend,ziehend (ohne Richtungsangabe),überfliegend (kein / nicht sicherer Zug),Mauserplatz,Nesterzählung
    <EMPTY> -> Junction_2
    <MISSING> -> Junction_2
    <NULL> -> Junction_2
    <UNFILTERED> -> Junction_2
    Fang zur Beringung -> Junction_2
    Flug zum / vom Schlafplatz -> Junction_2
    Gesang / Balz -> Junction_2
    N ziehend -> Junction_2
    NO ziehend -> Junction_2
    NW ziehend -> Junction_2
    Nahrung suchend -> Junction_2
    O ziehend -> Junction_2
    Revier (basierend auf mehreren Erfassungen) -> Junction_2
    S ziehend -> Junction_2
    SO ziehend -> Junction_2
    SW ziehend -> Junction_2
    Schlaf- / Sammelplatz -> Junction_2
    Totfund / Rupfung -> Junction_2
    W ziehend -> Junction_2
    rastend / ruhend -> Junction_2
    ziehend (ohne Richtungsangabe) -> Junction_2
    überfliegend (kein / nicht sicherer Zug) -> Junction_2
    Mauserplatz -> Junction_2
    Nesterzählung -> Junction_2
Junction_2
    -> AttributeValueMapper_2
AttributeValueMapper_2
    DIRECTION = Forward (Source To Destination)
    LUT = Fang zur Beringung,Scalene_triangle,Flug zum / vom Schlafplatz,Right_triangle,Gesang / Balz,Star,N ziehend,Parallelogram,NO ziehend,Rhombus,NW ziehend,Cross,Nahrung suchend,Oval,O ziehend,Nonagon,Revier (basierend auf mehreren Erfassungen),Octagon,S ziehend,Heptagon,SO ziehend,Hexagon,SW ziehend,Crescent,Schlaf- / Sammelplatz,Square,Totfund / Rupfung,Pentagon,W ziehend,Heart,rastend / ruhend,Circle,ziehend (ohne Richtungsangabe),Arrow,überfliegend (kein / nicht sicherer Zug),Triangle,Mauserplatz,Cube,Nesterzählung,Cylinder
    SRC = Vitality
    VAL_ATTR = Shape
    -> Flower_2 (writer SHAPEFILE_6)
Flower_2 (writer SHAPEFILE_6)
    attributes: Flower_Col char(254), Total_Coun number(11,0), Vitality char(254), Properties char(254), Date date, Type char(254), Code char(254), Latitude double, Longitude double, Precision char(254), Known char(254), Flower char(254), Shape char(254)
Flower_3 (reader SHAPEFILE_9)
    attributes: Month char(200), Day char(200), Year char(200), Key char(200), Flower_Col char(254), Total_Coun number(11,0), Vitality char(254), Properties char(254), Date date, Type char(254), Code char(254), Latitude double, Longitude double, Precision char(254), Known char(254), Flower char(254), Shape char(254), Precise char(254), Developed char(254)
    -> AttributeManager_3
AttributeManager_3
    ATTR_TABLE:
      RENAME_SET_VALUE Total_Coun > Count
      RENAME_SET_VALUE Precise > Location
      REMOVE Flower_Col
      REMOVE Vitality
      REMOVE Properties
      REMOVE Date
      REMOVE Type
      REMOVE Code
      REMOVE Precision
      REMOVE Known
    -> AttributeFilter_5
AttributeFilter_5
    ATTR_NAME = Shape
    ATTR_VALUES = <Empty>,<Missing>,<Null>,<Unfiltered>,Arrow,Circle,Crescent,Cross,Cube,Cylinder,Heart,Heptagon,Hexagon,Nonagon,Octagon,Oval,Parallelogram,Pentagon,Rhombus,Right_triangle,Scalene_triangle,Square,Star,Triangle
    <EMPTY> -> Junction_5
    <MISSING> -> Junction_5
    <NULL> -> Junction_5
    <UNFILTERED> -> Junction_5
    Arrow -> Junction_5
    Circle -> Junction_5
    Crescent -> Junction_5
    Cross -> Junction_5
    Cube -> Junction_5
    Cylinder -> Junction_5
    Heart -> Junction_5
    Heptagon -> Junction_5
    Hexagon -> Junction_5
    Nonagon -> Junction_5
    Octagon -> Junction_5
    Oval -> Junction_5
    Parallelogram -> Junction_5
    Pentagon -> Junction_5
    Rhombus -> Junction_5
    Right_triangle -> Junction_5
    Scalene_triangle -> Junction_5
    Square -> Junction_5
    Star -> Junction_5
    Triangle -> Junction_5
Junction_5
    -> AttributeValueMapper_5
AttributeValueMapper_5
    DEFAULT_VALUE = Unknown
    DIRECTION = Forward (Source To Destination)
    LUT = @Value(Shape),@Value(Shape)
    SRC = Shape
    VAL_ATTR = F_Shape
    -> AttributeManager_4
AttributeManager_4
    ATTR_TABLE:
      RENAME_SET_VALUE Count > F_Count
      REMOVE Shape
    -> Flower_Data (writer SHAPEFILE_10)
Flower_Data (writer SHAPEFILE_10)
    attributes: Flower char(254), F_Count number(11,0), F_Shape char(254), Month char(200), Day char(200), Year char(200), Key char(200), Developed char(254), Latitude double, Longitude double, Location char(254)
